import runpy
import traceback
from pathlib import Path

script = Path(__file__).with_suffix(".py")
try:
    runpy.run_path(str(script), run_name="__main__")
except Exception:
    traceback.print_exc()
    raise
