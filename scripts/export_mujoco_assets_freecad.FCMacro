import runpy
import sys
import traceback
from pathlib import Path

script = Path(__file__).with_suffix(".py")
try:
    forwarded = sys.argv[sys.argv.index("--") + 1 :] if "--" in sys.argv else []
    sys.argv = [str(script), *forwarded]
    runpy.run_path(str(script), run_name="__main__")
except Exception:
    traceback.print_exc()
    raise
